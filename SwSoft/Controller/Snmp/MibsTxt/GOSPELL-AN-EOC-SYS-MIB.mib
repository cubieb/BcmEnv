--------------------------------------------------------------------------------
-- File Name : GOSPELL-AN-EOC-SYS-MIB.mib
-- Date      : 2014-08-12
-- Author    : GOSPELL Nms dept.
--
-- Gospell Equipment Mib for EoC
--------------------------------------------------------------------------------

    GOSPELL-AN-EOC-SYS-MIB    DEFINITIONS ::= BEGIN
    IMPORTS
        RowStatus, DisplayString,TruthValue FROM SNMPv2-TC
        MODULE-IDENTITY, OBJECT-TYPE, Integer32, IpAddress  FROM SNMPv2-SMI;
--	gospell    					FROM GOSPELL-CMTS-MIB;
	
    gospell OBJECT IDENTIFIER ::= { enterprises 22764 }
    gsAn OBJECT IDENTIFIER ::= { gospell 1015 } 
    
    gsAnEocMib    MODULE-IDENTITY
        LAST-UPDATED    ""
        ORGANIZATION    "GOSPELL Corporation"
        CONTACT-INFO    "
                        Mail: Wangqs@gospell.com
                        Tel : 028-87839922"
        DESCRIPTION     "This MIB defines EoC Node managed objects."
        ::=  {  gsAn  3053  }  

    gsAnEocSysObjects       OBJECT IDENTIFIER   ::=  {  gsAnEocMib  1  }
    gsAnEocTrapObjects      OBJECT IDENTIFIER   ::=  {  gsAnEocMib  2  }
    
    gsAnEocSysMgmt          OBJECT IDENTIFIER   ::=  {  gsAnEocSysObjects  1  }  
    gsAnEocResTrapsGroup    OBJECT IDENTIFIER   ::=  {  gsAnEocTrapObjects 1  }

    --------------------------------------------------------------------------------
    -- 1.Error Code for Snmp Operation
    --------------------------------------------------------------------------------

    gsAnEocSnmpCmdErrCode   OBJECT-TYPE
        SYNTAX      Integer32
        MAX-ACCESS  read-only
        STATUS      current
        DESCRIPTION "Error code for SNMP set command.When agent excutes a snmp set, this variable should be maintained.Value 0 means success." 
        DEFVAL { 0 }
        ::=  {  gsAnEocSysObjects  1  }

    --------------------------------------------------------------------------------
    -- 2.Eoc System Management table
    --------------------------------------------------------------------------------

    gsAnEocSysMgmtTable   OBJECT-TYPE
        SYNTAX      SEQUENCE  OF  GsAnEocSysMgmtEntry
        MAX-ACCESS  not-accessible
        STATUS      current
        DESCRIPTION "This table includes the enable or disable plug and play of the Card."
        ::=  { gsAnEocSysObjects  2 }

    GsAnEocSysMgmtEntry   OBJECT-TYPE
        SYNTAX      GsAnEocSysMgmtEntry
        MAX-ACCESS  not-accessible
        STATUS      current
        DESCRIPTION "An entry in gsAnEocSysMgmtTable."
        INDEX       {  gsAnEocCltNo  }
        ::=  { gsAnEocSysMgmtTable 1 }

     GsAnEocSysMgmtEntry  ::=
        SEQUENCE {
            gsAnEocCltNo    Integer32,
            gsAnEocCltCpuLoad   Integer32,
            gsAnEocCltCpuLoadThreshold Integer32
        }

    gsAnEocCltNo  OBJECT-TYPE 
        SYNTAX          Integer32
        MAX-ACCESS      not-accessible
        STATUS          current
        DESCRIPTION     ""
        ::=  {  GsAnEocSysMgmtEntry  1  }

    gsAnEocCltCpuLoad  OBJECT-TYPE 
        SYNTAX          Integer32
        UNITS           "percent"
        MAX-ACCESS      read-only
        STATUS          current
        DESCRIPTION     "The current CPU load of this OLT module. "
        ::=  {  GsAnEocSysMgmtEntry  10  }

    gsAnEocCltCpuLoadThreshold  OBJECT-TYPE 
        SYNTAX          Integer32
        UNITS           "percent"
        MAX-ACCESS      read-write
        STATUS          current
        DESCRIPTION     "The CPU load threshold of this OLT module.When gsAnEocCltCpuLoad 
          is  higher than gsAnEocCltCpuLoadThreshold, gsAnEocCltCpuLoadAlarm trap
          should be generated by agent."
        ::=  {  GsAnEocSysMgmtEntry  11  }


    --------------------------------------------------------------------------------
    -- 3.definition of EoC traps
    --------------------------------------------------------------------------------

    --------------------------------------------------------------------------------
    -- 3.1 Resource Traps
    --------------------------------------------------------------------------------
    gsAnEocCltCpuLoadAlarm NOTIFICATION-TYPE
        OBJECTS { gsAnEocCltCpuLoad,gsAnEocCltCpuLoadThreshold }
        STATUS  current
        DESCRIPTION 
            "A gsAnEocCltCpuLoadAlarm trap indicates that the gsAnEocCltCpuLoad object of the CLT module 
            has exceed the configured threshold value of gsAnEocCltCpuLoadThreshold."
        ::= { gsAnEocResTrapsGroup 1 }

    gsAnEocCltCpuLoadAlarmCleared NOTIFICATION-TYPE
        OBJECTS { gsAnEocCltCpuLoad,gsAnEocCltCpuLoadThreshold }
        STATUS  current
        DESCRIPTION
            "It indicated that the agent has detected that the gsAnEocCltCpuLoad object of the CLT module
            has less than the configured threshold value of gsAnEocCltCpuLoadThreshold."
        ::= { gsAnEocResTrapsGroup 2 }

END
