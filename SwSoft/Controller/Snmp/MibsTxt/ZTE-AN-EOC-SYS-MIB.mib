--------------------------------------------------------------------------------
-- File Name : zxnm01-eoc-sys.mib
-- Date      : 2010-01-25
-- Author    : ZTE Nms dept.
--
-- Zte Equipment Mib for EoC
--------------------------------------------------------------------------------

    ZTE-AN-EOC-SYS-MIB    DEFINITIONS ::= BEGIN
    IMPORTS
        RowStatus, DisplayString,TruthValue FROM SNMPv2-TC
        MODULE-IDENTITY, OBJECT-TYPE, Integer32, IpAddress  FROM SNMPv2-SMI;
        
    zte OBJECT IDENTIFIER ::= { enterprises 3902 }
    zxAn OBJECT IDENTIFIER ::= { zte 1015 } 
    
    zxAnEocMib    MODULE-IDENTITY
        LAST-UPDATED    "2012101914Z"
        ORGANIZATION    "ZTE Corporation"
        CONTACT-INFO    "zhen weimin
                        Mail: zhen.weimin@zte.com.cn
                        Tel : 021-68896259"
        DESCRIPTION     "This MIB defines EoC Node managed objects."
        ::=  {  zxAn  3053  }  

    zxAnEocSysObjects       OBJECT IDENTIFIER   ::=  {  zxAnEocMib  1  }
    zxAnEocTrapObjects      OBJECT IDENTIFIER   ::=  {  zxAnEocMib  2  }
    
    zxAnEocSysMgmt          OBJECT IDENTIFIER   ::=  {  zxAnEocSysObjects  1  }  
    zxAnEocResTrapsGroup    OBJECT IDENTIFIER   ::=  {  zxAnEocTrapObjects 1  }

    --------------------------------------------------------------------------------
    -- 1.Error Code for Snmp Operation
    --------------------------------------------------------------------------------

    zxAnEocSnmpCmdErrCode   OBJECT-TYPE
        SYNTAX      Integer32
        MAX-ACCESS  read-only
        STATUS      current
        DESCRIPTION "Error code for SNMP set command.When agent excutes a snmp set, this variable should be maintained.Value 0 means success." 
        DEFVAL { 0 }
        ::=  {  zxAnEocSysObjects  1  }

    --------------------------------------------------------------------------------
    -- 2.Eoc System Management table
    --------------------------------------------------------------------------------

    zxAnEocSysMgmtTable   OBJECT-TYPE
        SYNTAX      SEQUENCE  OF  ZxAnEocSysMgmtEntry
        MAX-ACCESS  not-accessible
        STATUS      current
        DESCRIPTION "This table includes the enable or disable plug and play of the Card."
        ::=  { zxAnEocSysObjects  2 }

    ZxAnEocSysMgmtEntry   OBJECT-TYPE
        SYNTAX      ZxAnEocSysMgmtEntry
        MAX-ACCESS  not-accessible
        STATUS      current
        DESCRIPTION "An entry in zxAnEocSysMgmtTable."
        INDEX       {  zxAnEocCltNo  }
        ::=  { zxAnEocSysMgmtTable 1 }

     ZxAnEocSysMgmtEntry  ::=
        SEQUENCE {
            zxAnEocCltNo    Integer32,
            zxAnEocCltCpuLoad   Integer32,
            zxAnEocCltCpuLoadThreshold Integer32
        }

    zxAnEocCltNo  OBJECT-TYPE 
        SYNTAX          Integer32
        MAX-ACCESS      not-accessible
        STATUS          current
        DESCRIPTION     ""
        ::=  {  ZxAnEocSysMgmtEntry  1  }

    zxAnEocCltCpuLoad  OBJECT-TYPE 
        SYNTAX          Integer32
        UNITS           "percent"
        MAX-ACCESS      read-only
        STATUS          current
        DESCRIPTION     "The current CPU load of this OLT module. "
        ::=  {  ZxAnEocSysMgmtEntry  10  }

    zxAnEocCltCpuLoadThreshold  OBJECT-TYPE 
        SYNTAX          Integer32
        UNITS           "percent"
        MAX-ACCESS      read-write
        STATUS          current
        DESCRIPTION     "The CPU load threshold of this OLT module.When zxAnEocCltCpuLoad 
          is  higher than zxAnEocCltCpuLoadThreshold, zxAnEocCltCpuLoadAlarm trap
          should be generated by agent."
        ::=  {  ZxAnEocSysMgmtEntry  11  }


    --------------------------------------------------------------------------------
    -- 3.definition of EoC traps
    --------------------------------------------------------------------------------

    --------------------------------------------------------------------------------
    -- 3.1 Resource Traps
    --------------------------------------------------------------------------------
    zxAnEocCltCpuLoadAlarm NOTIFICATION-TYPE
        OBJECTS { zxAnEocCltCpuLoad,zxAnEocCltCpuLoadThreshold }
        STATUS  current
        DESCRIPTION 
            "A zxAnEocCltCpuLoadAlarm trap indicates that the zxAnEocCltCpuLoad object of the CLT module 
            has exceed the configured threshold value of zxAnEocCltCpuLoadThreshold."
        ::= { zxAnEocResTrapsGroup 1 }

    zxAnEocCltCpuLoadAlarmCleared NOTIFICATION-TYPE
        OBJECTS { zxAnEocCltCpuLoad,zxAnEocCltCpuLoadThreshold }
        STATUS  current
        DESCRIPTION
            "It indicated that the agent has detected that the zxAnEocCltCpuLoad object of the CLT module
            has less than the configured threshold value of zxAnEocCltCpuLoadThreshold."
        ::= { zxAnEocResTrapsGroup 2 }

END
